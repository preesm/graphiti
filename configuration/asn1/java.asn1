-- as per http://java.sun.com/javase/6/docs/platform/serialization/spec/protocol.html

Java DEFINITIONS ::= BEGIN

  Stream ::= SEQUENCE {
    magic BIT STRING ('aced'H),
    version BIT STRING ('0005'H),
    Contents
  }
  
  BlockData ::= CHOICE {
    BlockDataShort,
    BlockDataLong
  }
  
  BlockDataShort ::= SEQUENCE {
    tcBlockData BIT STRING ('77'H),
    size INTEGER (0..255),
    SEQUENCE (SIZE(size)) OF INTEGER (0..255)
  }

  BlockDataLong ::= SEQUENCE {
    tcBlockDataLong BIT STRING ('7A'H),
    size INTEGER (SIZE(32)),
    SEQUENCE (SIZE(size)) OF INTEGER (0..255)
  }
  
  ClassAnnotation ::= CHOICE {
    endBlockData BIT STRING ('78'H),
    SEQUENCE {
      Contents,
      endBlockData BIT STRING ('78'H)
    }
  }

  ClassDesc ::= CHOICE {
    NewClassDesc,
    nullReference BIT STRING ('70'H),
    PrevObject
  }
  
  ClassDescInfo ::= SEQUENCE {
    classDescFlags INTEGER (SIZE(8)),
    Fields,
    ClassAnnotation,
    superClassDesc ClassDesc
  }

  Content ::= CHOICE {
    Object,
    BlockData
  }

  Contents ::= SEQUENCE OF Content

  Exception ::= SEQUENCE {
    tcException BIT STRING ('7B'H),
    object UTF8String
  }
  
  Fields ::= SEQUENCE {
    count INTEGER (SIZE(16)),
    SEQUENCE (SIZE(count)) OF FieldDesc
  }
  
  FieldDesc ::= CHOICE {
    PrimitiveDesc,
    ObjectDesc
  }
  
  NewArray ::= SEQUENCE {
    tcArray BIT STRING ('75'H),
    ClassDesc,
    size INTEGER(SIZE(32))
    -- TODO: SEQUENCE (SIZE(size)) OF Value
  }
  
  NewClass ::= SEQUENCE {
    tcClass BIT STRING ('76'H),
    ClassDesc
  }
  
  NewClassDesc ::= CHOICE {
    SEQUENCE {
      tcClassDesc BIT STRING ('72'H),
      className UTF8String,
      serialVersionUID INTEGER (SIZE(64)),
      ClassDescInfo
    },
      
    SEQUENCE {
      tcProxyClassDesc BIT STRING ('7D'H),
      ProxyClassDescInfo
    }
  }

  NewEnum ::= SEQUENCE {
    tcEnum BIT STRING ('7E'H),
    ClassDesc,
    object UTF8String
  }
  
  NewObject ::= SEQUENCE {
    tcObject BIT STRING ('73'H),
    ClassDesc
    -- TODO: classdata[]
  }
  
  NewString ::= CHOICE {
    SEQUENCE {
      tcString BIT STRING ('74'H),
      UTF8String
    },
    
    SEQUENCE {
      tcLongString BIT STRING ('7C'H),
      LongUTF8String
    }
  }
  
  -- TODO:
  -- value
  -- classdata
  -- nowrclass
  -- wrclass
  -- objectAnnotation

  Object ::= CHOICE {
    NewObject,
    NewClass,
    NewArray,
    NewString,
    NewEnum,
    NewClassDesc,
    PrevObject,
    nullReference BIT STRING ('70'H),
    Exception,
    tcReset BIT STRING ('79'H)
  }
  
  ObjectDesc ::= SEQUENCE {
    ObjectTypeCode,
    fieldName UTF8String,
    className UTF8String
  }
  
  ObjectTypeCode ::= PrintableString (
    "[" | "L"
  )

  PrevObject ::= SEQUENCE {
    tcReference BIT STRING ('71'H),
    handle INTEGER(SIZE(32))
  }
  
  PrimitiveDesc ::= SEQUENCE {
    PrimitiveTypeCode,
    fieldName UTF8String
  }

  PrimitiveTypeCode ::= PrintableString (
    "B" | "C" | "D" | "F" | "I" | "J" | "S" | "Z"
  )
  
  ProxyClassDescInfo ::= SEQUENCE {
    count INTEGER (SIZE(32)),
    proxyInterfaceNames SEQUENCE (SIZE(count)) OF UTF8String,
    ClassAnnotation,
    superClassDesc ClassDesc
  }


END
